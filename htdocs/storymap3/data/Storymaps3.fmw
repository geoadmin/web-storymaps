FME workspace Storymaps3.fmw

Parameters:
- SourceDataset_POSTGIS = uvek   # Source PostGIS Dataset
- DestDataset_GEOJSON = .\stauanlage.geojson   # Destination GeoJSON File
- DestDataset_CSV = .\stauanlagen.csv   # Destination Comma Separated Value (CSV) Directory

Readers:
- POSTGIS_1: POSTGIS from $(SourceDataset_POSTGIS)

Writers:
- GEOJSON_1: GEOJSON to $(DestDataset_GEOJSON)
- CSV_1: CSV to $(DestDataset_CSV)

bfe.stauanlagen_bundesaufsicht (reader POSTGIS_1)
    attributes: reservoir_stabil_id int4, crestlevel float4, damheight float4, impoundmentlevel float4, riverid text, startsupervision text, endsupervision text, facility_stabil_id int4, facilityr2 int4, facilityr3 int4, damtype_en text, facilityr1 int4, facilityname text, reservoirname text, dam_stabil_id int8,PRIKEY, crestlength float4, has_picture int2, supervision_stabil_id int4, facaim_en text, damtype_fr text, lakename text, impoundmentvolume text, damtype_de text, facaim_fr text, facaim_de text, beginningofoperation text, lakeid text, damname text, rivername text, bgdi_modified timestamp,
      bgdi_created timestamp, bgdi_modified_by varchar(50), bgdi_created_by varchar(50), bgdi_id serial,PRIKEY, damtype int4, storagelevel float4
    -> stauanalgen (writer GEOJSON_1)
    -> stauanlagen (writer CSV_1)
stauanalgen (writer GEOJSON_1)
    attributes: reservoir_stabil_id int, crestlevel float, damheight float, impoundmentlevel float, riverid string, startsupervision string, endsupervision string, facility_stabil_id int, facilityr2 int, facilityr3 int, damtype_en string, facilityr1 int, facilityname string, reservoirname string, dam_stabil_id int, crestlength float, has_picture int, supervision_stabil_id int, facaim_en string, damtype_fr string, lakename string, impoundmentvolume string, damtype_de string, facaim_fr string, facaim_de string, beginningofoperation string, lakeid string, damname string, rivername string, bgdi_modified string,
      bgdi_created string, bgdi_modified_by string, bgdi_created_by string, bgdi_id int, damtype int, storagelevel float
stauanlagen (writer CSV_1)
    attributes: reservoir_stabil_id number(11,0), crestlevel number(15,7), damheight number(15,7), impoundmentlevel number(15,7), riverid char(254), startsupervision char(254), endsupervision char(254), facility_stabil_id number(11,0), facilityr2 number(11,0), facilityr3 number(11,0), damtype_en char(254), facilityr1 number(11,0), facilityname char(254), reservoirname char(254), dam_stabil_id number(11,0), crestlength number(15,7), has_picture number(6,0), supervision_stabil_id number(11,0), facaim_en char(254), damtype_fr char(254), lakename char(254), impoundmentvolume char(254), damtype_de char(254), facaim_fr char(254), facaim_de char(254), beginningofoperation char(254), lakeid char(254), damname char(254), rivername char(254), bgdi_modified char(20),
      bgdi_created char(20), bgdi_modified_by char(50), bgdi_created_by char(50), bgdi_id number(11,0), damtype number(11,0), storagelevel number(15,7)
